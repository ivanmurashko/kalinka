KLK-HTTPSTREAMER-MIB DEFINITIONS::= BEGIN
-- =================================
-- .1.3.6.1.4.1.31106.5
-- .iso.org.dod.internet.private.enterprises.klk.httpstreamer

-- check MIB file:
--   snmptranslate -M+. -mKLK-HTTPSTREAMER-MIB -Tp -IR httpstreamer

-- getting a OID:
--   snmptranslate -M+. -mKLK-HTTPSTREAMER-MIB -IR  klkBrokenPackageTrap

-- getting a textual OID:
--   snmptranslate -On -M+. -mKLK-HTTPSTREAMER-MIB -IR klkBrokenPackageTrap

-- getting a description:
--   snmptranslate -Td -M+. -mKLK-HTTPSTREAMER-MIB -IR klkBrokenPackageTrap

-- generate a code
--  env MIBS="+KLK-HTTPSTREAMER-MIB" mib2c -c mib2c.iterate.conf klkStatusTable
-- =================================
-- =================================
IMPORTS
  enterprises                                FROM SNMPv2-SMI,
  klk                                        FROM KLK-MIB
  OBJECT-TYPE, MODULE-IDENTITY, Integer32    FROM SNMPv2-SMI
  DisplayString	                             FROM SNMPv2-TC;

--
-- A brief description and update information about this mib.
--
httpstreamer MODULE-IDENTITY
  LAST-UPDATED "200905240000Z"
  ORGANIZATION "Kalinka Team"
  CONTACT-INFO "Ivan Murashko
               "
  DESCRIPTION  "MIB for Kalinka HTTP streamer application module
               "
  ::= { klk 5 }

klkBrokenPackageTrap NOTIFICATION-TYPE
  STATUS current
  DESCRIPTION "A broken package was gotten. The input route name will
  be a value of the trap"
  ::= { httpstreamer 1 }

klkStatusTable OBJECT-TYPE
  SYNTAX     SEQUENCE OF klkStatusEntry
  MAX-ACCESS not-accessible
  STATUS     current
  DESCRIPTION
    "A list of httpstreamer statuses."
  ::= { httpstreamer 2 }

klkStatusEntry OBJECT-TYPE
  SYNTAX     KLKHTTPStatusEntry
  MAX-ACCESS not-accessible
  STATUS     current
  DESCRIPTION
    "An entry containing information applicable to a
    one input source (status info)"
  INDEX { klkIndex }
  ::= { klkStatusTable 1 }

KLKHTTPStatusEntry ::=
  SEQUENCE {
    klkIndex             Counter32,
    klkOutputPath        DisplayString,
    klkInputAddr         DisplayString,
    klkInputRate         Integer32,
    klkOutputRate        Integer32,
    klkOutputConn        Counter32,
    klkBrokenPackages    Counter32
  }

klkIndex OBJECT-TYPE
  SYNTAX      Counter32
  MAX-ACCESS  read-only
  STATUS      current
  DESCRIPTION
          "The record id"
  ::= { klkStatusEntry 1 }

klkOutputPath OBJECT-TYPE
  SYNTAX      DisplayString (SIZE (0..255))
  MAX-ACCESS  read-only
  STATUS      current
  DESCRIPTION
          "Output path. The HTTP server output path."
  ::= { klkStatusEntry 2 }

klkInputAddr OBJECT-TYPE
  SYNTAX      DisplayString (SIZE (0..255))
  MAX-ACCESS  read-only
  STATUS      current
  DESCRIPTION
          "Input address. Input data source address"
  ::= { klkStatusEntry 3 }

klkInputRate OBJECT-TYPE
  SYNTAX      Integer32
  MAX-ACCESS  read-only
  STATUS      current
  DESCRIPTION
          "Input data transfer rate in bytes per second"
  ::= { klkStatusEntry 4 }

klkOutputRate OBJECT-TYPE
  SYNTAX      Integer32
  MAX-ACCESS  read-only
  STATUS      current
  DESCRIPTION
          "Ouput data transfer rate in bytes per second"
  ::= { klkStatusEntry 5 }

klkOutputConn OBJECT-TYPE
  SYNTAX      Counter32
  MAX-ACCESS  read-only
  STATUS      current
  DESCRIPTION
          "Number of active output connections"
  ::= { klkStatusEntry 6 }

klkBrokenPackages OBJECT-TYPE
  SYNTAX      Counter32
  MAX-ACCESS  read-only
  STATUS      current
  DESCRIPTION
          "Broken packages count"
  ::= { klkStatusEntry 7 }

END
