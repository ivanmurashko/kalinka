KLK-DVB-MIB DEFINITIONS::= BEGIN
-- =================================
-- .1.3.6.1.4.1.31106.3
-- .iso.org.dod.internet.private.enterprises.klk.dvb

-- check MIB file:
--   snmptranslate -M+. -mKLK-DVB-MIB -Tp -IR dvb

-- getting a OID:
--   snmptranslate -M+. -mKLK-DVB-MIB -IR klkNoSignal

-- getting a textual OID:
--   snmptranslate -On -M+. -mKLK-DVB-MIB -IR klkNoSignal

-- getting a description:
--   snmptranslate -Td -M+. -mKLK-DVB-MIB -IR klkNoSignal

-- generate a code
--  env MIBS="+KLK-DVB-MIB" mib2c -c mib2c.iterate.conf klkStatusTable


-- =================================
-- =================================
IMPORTS
  enterprises                                FROM SNMPv2-SMI
  klk                                        FROM KLK-MIB
  OBJECT-TYPE, MODULE-IDENTITY, Integer32    FROM SNMPv2-SMI
  DisplayString, TruthValue                  FROM SNMPv2-TC;


--
-- A brief description and update information about this mib.
--
dvb MODULE-IDENTITY
  LAST-UPDATED "200905260000Z"
  ORGANIZATION "Kalinka Team"
  CONTACT-INFO "Ivan Murashko
               "
  DESCRIPTION  "MIB for Kalinka mediaserver DVB module
               "
  ::= { klk 3 }

traps OBJECT IDENTIFIER ::= { dvb 1 }

klkNoSignal NOTIFICATION-TYPE
  STATUS current
  DESCRIPTION "The forntend (card) has lost signal. The device UUID is
  set as a string"
  ::= { traps 1 }

klkTimeOut NOTIFICATION-TYPE
  STATUS current
  DESCRIPTION "No lock within last 3*60 seconds. The device UUID is
  set as a string"
  ::= { traps 2 }

klkBadBER NOTIFICATION-TYPE
  STATUS current
  DESCRIPTION "The forntend (card) has bad Bit Error Rate. The alert
  will be sent after 3 bit rate errors. The device UUID is
  set as a string"
  ::= { traps 3 }

klkBadUNC NOTIFICATION-TYPE
  STATUS current
  DESCRIPTION "The forntend (card) has bad uncorrected block count
  (UNC). The alert  will be sent after the counter reach 3. The device
  UUID is set as a string"
  ::= { traps 4 }

klkBadSNR NOTIFICATION-TYPE
  STATUS current
  DESCRIPTION "The forntend (card) has bad signal to noise ratio
  (SNR). The alert will be sent after the value less 57999. The device
  UUID is set as a string"
  ::= { traps 5 }

klkBadSignal NOTIFICATION-TYPE
  STATUS current
  DESCRIPTION "The forntend (card) has bad signal strength.
  The alert will be sent after the value less 50000. The device UUID
  is set as a string"
  ::= { traps 6 }

klkDevLost NOTIFICATION-TYPE
  STATUS current
  DESCRIPTION "The device does not exist. The device UUID
  is set as a string"
  ::= { traps 7 }

klkStatusTable OBJECT-TYPE
  SYNTAX     SEQUENCE OF klkStatusEntry
  MAX-ACCESS not-accessible
  STATUS     current
  DESCRIPTION
    "A list of dvb statuses."
  ::= { dvb 2 }

klkStatusEntry OBJECT-TYPE
  SYNTAX     KLKDVBStatusEntry
  MAX-ACCESS not-accessible
  STATUS     current
  DESCRIPTION
    "An entry containing information applicable to a
    dvb card (status info)"
  INDEX { klkIndex }
  ::= { klkStatusTable 1 }

KLKDVBStatusEntry ::=
  SEQUENCE {
    klkIndex      Counter32,
    klkCardName   DisplayString,
    klkCardType   DisplayString,
    klkAdapter    Integer32,
    klkFrontend   Integer32,
    klkHasLock    TruthValue,
    klkSignal     Integer32,
    klkSNR        Integer32,
    klkBER        Integer32,
    klkUNC        Counter32,
    klkRate       Integer32
  }

klkIndex OBJECT-TYPE
  SYNTAX      Counter32
  MAX-ACCESS  read-only
  STATUS      current
  DESCRIPTION
          "The record id"
  ::= { klkStatusEntry 1 }

klkCardName OBJECT-TYPE
  SYNTAX      DisplayString (SIZE (0..255))
  MAX-ACCESS  read-only
  STATUS      current
  DESCRIPTION
          "The DVB card name stored at the DB"
  ::= { klkStatusEntry 2 }

klkCardType OBJECT-TYPE
  SYNTAX      DisplayString (SIZE (0..255))
  MAX-ACCESS  read-only
  STATUS      current
  DESCRIPTION
          "The DVB card type DVB-T/S"
  ::= { klkStatusEntry 3 }

klkAdapter OBJECT-TYPE
  SYNTAX      Integer32
  MAX-ACCESS  read-only
  STATUS      current
  DESCRIPTION
          "The DVB card adapter number"
  ::= { klkStatusEntry 4 }

klkFrontend OBJECT-TYPE
  SYNTAX      Integer32
  MAX-ACCESS  read-only
  STATUS      current
  DESCRIPTION
          "The DVB card frontend number"
  ::= { klkStatusEntry 5 }

klkHasLock OBJECT-TYPE
  SYNTAX      TruthValue
  MAX-ACCESS  read-only
  STATUS      current
  DESCRIPTION
          "The DVB card lock status"
  ::= { klkStatusEntry 6 }

klkSignal OBJECT-TYPE
  SYNTAX      Integer32
  MAX-ACCESS  read-only
  STATUS      current
  DESCRIPTION
          "Signal strength on the card"
  ::= { klkStatusEntry 7 }

klkSNR OBJECT-TYPE
  SYNTAX      Integer32
  MAX-ACCESS  read-only
  STATUS      current
  DESCRIPTION
          "Signal/noise ratio for the card"
  ::= { klkStatusEntry 8 }

klkBER OBJECT-TYPE
  SYNTAX      Integer32
  MAX-ACCESS  read-only
  STATUS      current
  DESCRIPTION
          "Bit error ratio on the card"
  ::= { klkStatusEntry 9 }

klkUNC OBJECT-TYPE
  SYNTAX      Counter32
  MAX-ACCESS  read-only
  STATUS      current
  DESCRIPTION
          "Uncorrect block count on the card"
  ::= { klkStatusEntry 10 }

klkRate OBJECT-TYPE
  SYNTAX      Integer32
  MAX-ACCESS  read-only
  STATUS      current
  DESCRIPTION
          "DVB data read rate in bytes per second"
  ::= { klkStatusEntry 11 }

END
